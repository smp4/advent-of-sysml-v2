package AdventOfSysMLv2_Lesson06 {
    part def SantaSleigh {
        // Components of the sleigh
        part cockpit {
            doc
            /* This is where driver sits. */
            ref item driver;
        }
    }
}
