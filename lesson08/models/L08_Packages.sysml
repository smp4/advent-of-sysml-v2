package L08_Packages {
    package SleighDesign {
        part def SantaSleigh {
            // ...
        }
    }

    package Entities {
        part def Reindeer {
            // ...
        }
    }

    package Datatypes {
        enum def Color {
            // ...
        }
    }

    package BaseComponents {
        part def NaughtyNiceDashboard;

        abstract part def CargoBay {
            // ...
        }

        abstract item def Bag {
            // ...
        }
    }
}
